module deviation {
  yang-version 1.1;
  namespace "urn:ietf:params:xml:ns:yang:deviation";
  prefix dev;

  import model {prefix mo;}

    deviation /mo:data-container/mo:list-data/mo:year {
        description "not-supported.";
        deviate not-supported;
    }
    deviation /mo:data-container/mo:list-data/mo:month {
        description "not-supported.";
        deviate not-supported;
    }
}
